; Diagnostico read-only de entidades. Ejecutar solo sobre copia identificada.
; No modifica coordenadas, tipos, XDATA, capas ni layout. No acredita CRS.
(defun dc:q (value / result code)
  (setq result "\"")
  (foreach code (vl-string->list value)
    (setq result (strcat result (cond ((= code 34) "\\\"") ((= code 92) "\\\\")
      ((= code 10) "\\n") ((= code 13) "\\r") ((= code 9) "\\t")
      ((< code 32) " ") (T (chr code))))))
  (strcat result "\""))
(defun dc:join (items / result)
  (setq result "")
  (foreach item items (setq result (strcat result (if (= result "") "" ",") item))) result)
(defun dc:v (value)
  (cond ((null value) "null") ((= (type value) 'STR) (dc:q value))
    ((= (type value) 'INT) (itoa value)) ((= (type value) 'REAL) (rtos value 2 16))
    ((listp value) (strcat "[" (dc:join (mapcar 'dc:v value)) "]"))
    (T (dc:q (vl-princ-to-string value)))))
(defun dc:emit (kind pairs)
  (write-line (strcat "{\"kind\":" (dc:q kind)
    (if pairs "," "") (dc:join (mapcar '(lambda (p) (strcat (dc:q (car p)) ":" (dc:v (cdr p)))) pairs)) "}") dc:*stream*))
(defun dc:fields (data fields)
  (mapcar '(lambda (p) (cons (car p) (cdr (assoc (cdr p) data)))) fields))
(defun dc:paper (point) (trans (trans point 0 2) 2 3))
(defun dc:anchor (data / p)
  (command "_.MSPACE")
  (setvar "CVPORT" (cdr (assoc 69 data)))
  (setq p '(500000.0 3600000.0 0.0))
  (dc:emit "projection_anchor" (list (cons "handle" (cdr (assoc 5 data)))
    (cons "world" p) (cons "paper" (dc:paper p))
    (cons "paper_x" (dc:paper (mapcar '+ p '(1000.0 0.0 0.0))))
    (cons "paper_y" (dc:paper (mapcar '+ p '(0.0 1000.0 0.0))))
    (cons "delta_model" 1000.0)))
  (command "_.PSPACE"))
(defun dc:export (expected file / oldtab oldtile s i e d x id owner layer points bounds b a ad)
  (datra:guard expected)
  (setq dc:*stream* (open file "w") oldtab (getvar "CTAB") oldtile (getvar "TILEMODE"))
  (dc:emit "environment" (mapcar '(lambda (n) (cons n (getvar n)))
    '("CTAB" "TILEMODE" "INSUNITS" "UCSNAME" "WORLDUCS" "UCSORG" "UCSXDIR" "UCSYDIR" "PDFSHX" "ACADVER")))
  (foreach name (datra:layouts)
    (dc:emit "layout" (cons (cons "name" name) (dc:fields (entget (datra:layout-entity name))
      '(("device" . 2) ("media" . 4) ("paper_width" . 44) ("paper_height" . 45)
        ("units" . 72) ("rotation" . 73) ("plot_type" . 74) ("plot_flags" . 70)
        ("plot_origin" . 46) ("scale_numerator" . 142) ("scale_denominator" . 143))))))
  (setq b (tblnext "LAYER" T))
  (while b (dc:emit "layer" (dc:fields b '(("name" . 2) ("color" . 62) ("flags" . 70) ("plot" . 290)))) (setq b (tblnext "LAYER")))
  (setq s (ssget "_X") i 0)
  (if s (repeat (sslength s)
    (setq e (ssname s i) i (1+ i) d (entget e '("DATRA_CFE")) x (assoc -3 d) id nil owner nil)
    (if x (setq owner (cdr (nth 1 (cadr x))) id (cdr (nth 2 (cadr x)))))
    (cond
      ((= "VIEWPORT" (cdr (assoc 0 d)))
        (dc:emit "viewport" (append (dc:fields d '(("handle" . 5) ("layout" . 410) ("layer" . 8)
          ("center_paper" . 10) ("width_paper" . 40) ("height_paper" . 41) ("view_center_dcs" . 12)
          ("direction_wcs" . 16) ("target_wcs" . 17) ("view_height_model" . 45) ("twist" . 51)
          ("flags" . 90) ("status" . 68) ("number" . 69) ("lens" . 42)))
          (list (cons "frozen_layers" (mapcar '(lambda (p) (cdr (assoc 2 (entget (cdr p)))))
            (vl-remove-if-not '(lambda (p) (= (car p) 331)) d)))))))
      (id
        (dc:emit "owned" (append (list (cons "id" id) (cons "owner" owner))
          (dc:fields d '(("handle" . 5) ("type" . 0) ("space" . 410) ("layer" . 8) ("position" . 10)
            ("block" . 2) ("height" . 40) ("scale_x" . 41) ("scale_y" . 42) ("scale_z" . 43)
            ("rotation" . 50) ("value" . 1) ("style" . 7) ("normal" . 210)))
          (if (= "TEXT" (cdr (assoc 0 d))) (list (cons "textbox_local" (textbox d)))))))
      ((= "Model" (cdr (assoc 410 d)))
        ; Los puntos de control son muestras, no extents exactos de curvas/bloques.
        (setq points (mapcar 'cdr (vl-remove-if-not '(lambda (p) (member (car p) '(10 11))) d)))
        (dc:emit "inherited_model" (append (dc:fields d '(("type" . 0) ("layer" . 8))) (list (cons "points" points))))))
    (if (and (= "INSERT" (cdr (assoc 0 d))) (= "DATRA_CAJETIN_A1" (cdr (assoc 2 d))) (= (cdr (assoc 66 d)) 1))
      (progn (setq a (entnext e))
        (while (and a (/= "SEQEND" (cdr (assoc 0 (setq ad (entget a))))))
          (dc:emit "attribute" (append (list (cons "layout" (cdr (assoc 410 d))))
            (dc:fields ad '(("tag" . 2) ("value" . 1) ("position" . 10) ("height" . 40)))))
          (setq a (entnext a)))))))
  (setvar "TILEMODE" 1)
  (command "_.REGEN")
  (dc:emit "model_extents" (list (cons "minimum" (getvar "EXTMIN")) (cons "maximum" (getvar "EXTMAX"))))
  (setvar "TILEMODE" 0)
  (foreach name (datra:layouts)
    (if (/= name "Model")
      (progn (setvar "CTAB" name) (command "_.PSPACE")
        (setq s (ssget "_X" (list '(0 . "VIEWPORT") (cons 410 name))) i 0)
        (if s (repeat (sslength s)
          (setq d (entget (ssname s i)) i (1+ i))
          (if (and (> (cdr (assoc 69 d)) 1) (> (cdr (assoc 68 d)) 0))
            (progn
              (setq b (vl-catch-all-apply 'dc:anchor (list d)))
              (if (vl-catch-all-error-p b) (dc:emit "projection_error"
                (list (cons "handle" (cdr (assoc 5 d))) (cons "reason" (vl-catch-all-error-message b)))))
          )))))))
  (setvar "TILEMODE" oldtile)
  (if (= oldtile 0) (setvar "CTAB" oldtab))
  (close dc:*stream*) (princ))
(princ)
