; DATRA CFE - runtime versionado. Solo actua sobre copia de DWG exacta.
; Simbolos ESQUEMATICOS. No certifica CRS, materiales, DWT ni impresion.
(setq datra:*ready* nil datra:*height* 1.8)

(defun datra:fail (message)
  (setq datra:*failure* message)
  (exit))

(defun datra:guard (expected / actual)
  (setq actual (strcat (getvar "DWGPREFIX") (getvar "DWGNAME")))
  (if (/= (strcase (vl-string-translate "\\" "/" actual))
          (strcase (vl-string-translate "\\" "/" expected)))
    (datra:fail "DATRA: abra unicamente la COPIA indicada en el reporte CAD")))

(defun datra:snapshot (/ s i e d a result)
  (setq s (ssget "_X" '((-4 . "<OR") (-3 ("DATRA_CFE"))
    (0 . "VIEWPORT") (2 . "DATRA_CAJETIN_A1")
    (8 . "DATRA_A1_SIMBOLOS,DATRA_A1_TEXTO") (-4 . "OR>"))) i 0)
  (if s (repeat (sslength s)
    (setq e (ssname s i) i (1+ i) d (entget e '("DATRA_CFE")) result (cons (cons e d) result))
    (if (and (= (cdr (assoc 0 d)) "INSERT") (= (cdr (assoc 66 d)) 1))
      (progn (setq a (entnext e))
        (while (and a (/= "SEQEND" (cdr (assoc 0 (entget a)))))
          (setq result (cons (cons a (entget a)) result) a (entnext a)))))))
  (setq e (tblobjname "BLOCK" "DATRA_CAJETIN_A1"))
  (if e
    (progn
      (setq e (entnext e))
      (while (and e (/= "ENDBLK" (cdr (assoc 0 (setq d (entget e))))))
        (if (and (= "TEXT" (cdr (assoc 0 d)))
                 (member (cdr (assoc 1 d)) '("CRS VALIDADO" "CRS APLICADO")))
          (setq result (cons (cons e d) result)))
        (setq e (entnext e)))))
  result)

(defun datra:restore (snapshot / e item d)
  ; Core Console puede mantener un grupo SCRIPT activo aun tras UNDO END.
  ; Diario explícito de entidades propias: no confiar en un mensaje de UNDO.
  (foreach e datra:*created* (if (entget e) (entdel e)))
  (foreach item snapshot
    (setq e (car item) d (cdr item))
    (if (not (entget e)) (entdel e))
    ; VIEWPORT no admite entmod; el viewport anterior solo se había eliminado.
    (if (/= "VIEWPORT" (cdr (assoc 0 d))) (entmod d)))
  (command "_.REGENALL"))

(defun datra:run (fn / result snapshot name)
  (setq datra:*ready* nil datra:*failure* nil)
  (setq snapshot (datra:snapshot) datra:*created* nil datra:*new-layouts* nil
        datra:*symbol-scales* nil datra:*main-layout* nil)
  (command "_.UNDO" "_Begin")
  (setq result (vl-catch-all-apply fn nil))
  (command "_.UNDO" "_End")
  (if (or datra:*failure* (vl-catch-all-error-p result))
    (progn (setq datra:*ready* nil)
      (command "_.U")
      (datra:restore snapshot)
      (foreach name datra:*new-layouts*
        (if (member name (datra:layouts))
          (progn (setvar "CTAB" "Model") (command "_.-LAYOUT" "_Delete" name))))
      (alert (strcat "DATRA FALLIDO: " (if datra:*failure* datra:*failure* (vl-catch-all-error-message result))
        ". Geometria propia restaurada por diario; no guardar como FINAL. Revisar reporte."))))
  (princ))

(defun datra:layer (name color)
  (if (not (tblsearch "LAYER" name))
    (entmake (list '(0 . "LAYER") '(100 . "AcDbSymbolTableRecord")
       '(100 . "AcDbLayerTableRecord") (cons 2 name) '(70 . 0)
       (cons 62 color) '(6 . "Continuous")))))

(defun datra:block (name kind)
  (if (not (tblsearch "BLOCK" name))
    (progn
      (entmake (list '(0 . "BLOCK") (cons 2 name) '(70 . 0) '(10 0.0 0.0 0.0)))
      (cond
        ((= kind "CAJA_EMP")
          (entmake '((0 . "LWPOLYLINE") (100 . "AcDbEntity") (8 . "0")
            (100 . "AcDbPolyline") (90 . 4) (70 . 1)
            (10 -0.45 -0.45) (10 0.45 -0.45) (10 0.45 0.45) (10 -0.45 0.45))))
        (T (entmake '((0 . "CIRCLE") (8 . "0") (10 0.0 0.0 0.0) (40 . 0.45)))))
      (if (= kind "EXCEDENTE")
        (entmake '((0 . "LINE") (8 . "0") (10 -0.65 0.0 0.0) (11 0.65 0.0 0.0))))
      (entmake '((0 . "ENDBLK"))))))

(defun datra:layouts (/ result)
  (foreach item (entget (cdr (assoc -1 (dictsearch (namedobjdict) "ACAD_LAYOUT"))))
    (if (= (car item) 3) (setq result (cons (cdr item) result))))
  result)

(defun datra:layout-entity (name)
  (cdr (assoc -1 (dictsearch
    (cdr (assoc -1 (dictsearch (namedobjdict) "ACAD_LAYOUT"))) name))))

(defun datra:plot-settings (data settings / active result pair)
  (foreach pair data
    (if (= (car pair) 100) (setq active (= (cdr pair) "AcDbPlotSettings")))
    (if (and active (assoc (car pair) settings)) (setq pair (assoc (car pair) settings)))
    (setq result (cons pair result)))
  (reverse result))

(defun datra:layout (name / lay data)
  ; Copiar el layout de marco existente, nunca reconstruir Tijuana.
  (if (not (member name (datra:layouts)))
    (if (member "Layout1" (datra:layouts))
      (command "_.-LAYOUT" "_Copy" "Layout1" name)
      (datra:fail "Falta Layout1 de la base DATRA: acreditar perfil de plantilla")))
  (setq lay (datra:layout-entity name) data (entget lay))
  (if (not (and (equal (cdr (assoc 44 data)) 841.0 0.1)
                (equal (cdr (assoc 45 data)) 594.0 0.1)))
    (datra:fail "Perfil de papel de base no es A1 horizontal: acreditar plantilla"))
  (if (not (entmod (datra:plot-settings data
    '((72 . 1) (73 . 0) (74 . 5) (75 . 16) (142 . 1.0) (143 . 1.0) (147 . 1.0)))))
    (datra:fail "No se pudieron configurar unidades/escala de layout"))
  (setvar "CTAB" name)
  lay)

(defun datra:configure (expected owner layout mode meters / lay layerdata)
  (datra:guard expected)
  (setq datra:*owner* owner datra:*layout* layout datra:*mode* mode)
  (foreach pair '(("DATRA_POSTE" . 1) ("DATRA_CAJA_EMP" . 3) ("DATRA_EXCEDENTE" . 5)
                  ("DATRA_TEXTO" . 7) ("DATRA_RUTA" . 2) ("DATRA_DISTANCIA" . 4)
                  ("DATRA_CONTROL" . 6))
    (datra:layer (car pair) (cdr pair)))
  (datra:layer "DATRA_VIEWPORTS" 8)
  (setq layerdata (entget (tblobjname "LAYER" "DATRA_VIEWPORTS")))
  (if (assoc 290 layerdata)
    (setq layerdata (subst '(290 . 0) (assoc 290 layerdata) layerdata))
    (setq layerdata (append layerdata '((290 . 0)))))
  (entmod layerdata)
  (if (not (tblsearch "STYLE" "DATRA_SIMPLE_V1"))
    (entmake '((0 . "STYLE") (100 . "AcDbSymbolTableRecord") (100 . "AcDbTextStyleTableRecord")
       (2 . "DATRA_SIMPLE_V1") (70 . 0) (40 . 0.0) (41 . 1.0) (50 . 0.0)
       (71 . 0) (42 . 2.5) (3 . "txt.shx") (4 . ""))))
  (datra:block "DATRA_POSTE_V1" "POSTE")
  (datra:block "DATRA_CAJA_EMP_V1" "CAJA_EMP")
  (datra:block "DATRA_EXCEDENTE_V1" "EXCEDENTE")
  (if meters (setvar "INSUNITS" 6))
  (setvar "LUNITS" 2)
  ; Evitar decenas de miles de anotaciones SHX que impiden abrir el PDF.
  ; Conserva los glifos visibles; solo desactiva comentarios de texto SHX.
  (setvar "PDFSHX" 0)
  (regapp "DATRA_CFE")
  (datra:layout layout)
  (setq datra:*ready* T)
  (princ "\nDATRA CP03: configurado. Base y mapa conservados; requiere revision nativa A1."))

(defun datra:tag (entity id / data)
  (if (not entity) (datra:fail "No se pudo crear entidad CAD"))
  (setq data (entget entity))
  (if (not (entmod (append data (list (list -3 (list "DATRA_CFE" (cons 1000 datra:*owner*) (cons 1000 id)))))))
    (datra:fail "No se pudo persistir XDATA de la entidad"))
  entity)

(defun datra:make (data)
  ; entmake asigna propietario del espacio actual; no entmakex huerfano.
  (if (not (entmake data)) (datra:fail "entmake no creo entidad"))
  (setq datra:*created* (cons (entlast) datra:*created*))
  (entlast))

(defun datra:owned (entity / x)
  (setq x (assoc -3 (entget entity '("DATRA_CFE"))))
  (and x (= datra:*owner* (cdr (assoc 1000 (cdr (cadr x)))))))

(defun datra:erase-owned (space / sel i entity)
  (setq sel (ssget "_X" (append '((-3 ("DATRA_CFE"))) (if space (list (cons 410 space))))))
  (if sel
    (progn
      (if space (setvar "CTAB" space))
      (setq i 0)
      (repeat (sslength sel)
        (setq entity (ssname sel i) i (1+ i))
        (if (datra:owned entity) (entdel entity))))))

(defun datra:begin (expected owner layout mode / space)
  (datra:guard expected)
  (if (or (not (tblsearch "BLOCK" "DATRA_POSTE_V1"))
          (not (tblsearch "STYLE" "DATRA_SIMPLE_V1"))
          (not (member layout (datra:layouts))))
    (datra:fail "Ejecute primero SCR01 en esta copia"))
  (setq datra:*owner* owner datra:*layout* layout datra:*mode* mode
        datra:*points* 0 datra:*edges* 0 datra:*ready* T)
  (regapp "DATRA_CFE")
  (if datra:*main-layout*
    (foreach space (datra:layouts) (datra:erase-owned space))
    (datra:erase-owned nil))
  (setvar "CTAB" "Model"))

(defun datra:text (id layer point height value paper / entity)
  (if paper (setvar "CTAB" datra:*layout*))
  (setq entity (datra:make (list '(0 . "TEXT") (cons 8 layer)
    (cons 10 point) (cons 40 height) (cons 1 value) '(7 . "DATRA_SIMPLE_V1")
    (cons 67 (if paper 1 0)) (cons 410 (if paper datra:*layout* "Model")))))
  (datra:tag entity id))

(defun datra:point (id block kind x y label geo / entity h)
  (if (not datra:*ready*) (datra:fail "Sesion DATRA no habilitada"))
  (setq h (if datra:*symbol-scales* (cdr (assoc kind datra:*symbol-scales*)) datra:*height*))
  (setq entity (datra:make (list '(0 . "INSERT") (cons 2 block) (cons 8 (strcat "DATRA_" kind))
     (list 10 x y 0.0) (cons 41 h) (cons 42 h) (cons 43 h) '(67 . 0) '(410 . "Model"))))
  (datra:tag entity id)
  (if (not datra:*symbol-scales*)
    (progn
      (datra:text id "DATRA_TEXTO" (list (+ x h) (+ y h) 0.0) h label nil)
      (datra:text id "DATRA_TEXTO" (list (+ x h) (- y h) 0.0) (* h (/ 2.5 3.0)) geo nil)))
  (setq datra:*points* (1+ datra:*points*)))

(defun datra:edge (id x1 y1 x2 y2 label / entity)
  (if (not datra:*ready*) (datra:fail "Sesion DATRA no habilitada"))
  (setq entity (datra:make (list '(0 . "LWPOLYLINE") '(100 . "AcDbEntity")
    '(8 . "DATRA_RUTA") '(67 . 0) '(410 . "Model") '(100 . "AcDbPolyline")
    '(90 . 2) '(70 . 0) (list 10 x1 y1) (list 10 x2 y2))))
  (datra:tag entity id)
  (datra:text id "DATRA_DISTANCIA" (list (/ (+ x1 x2) 2.0) (/ (+ y1 y2) 2.0) 0.0)
    (* datra:*height* 0.8) label nil)
  (setq datra:*edges* (1+ datra:*edges*)))

(defun datra:cajetin (counts / s e a d found tags values key pending)
  ; Correspondencia observada en DATRA_CAJETIN_A1, no coordenadas supuestas.
  ; No tocar atributos de Layout1 ni entidades de otras plantillas.
  (setq s (ssget "_X" (list '(0 . "INSERT") '(2 . "DATRA_CAJETIN_A1")
    (cons 410 datra:*layout*))) tags '("TOTAL_POSTES" "TOTAL_CAJAS" "TOTAL_EXCEDENTES"))
  (if (and s (= (sslength s) 1))
    (progn
      (setq e (ssname s 0) a (entnext e))
      (while (and a (/= "SEQEND" (cdr (assoc 0 (setq d (entget a))))))
        (if (and (= "ATTRIB" (cdr (assoc 0 d))) (member (cdr (assoc 2 d)) tags))
          (setq found (cons (cons (cdr (assoc 2 d)) a) found)))
        (setq a (entnext a)))
      (if (and (= (length found) 3) (assoc "TOTAL_POSTES" found)
               (assoc "TOTAL_CAJAS" found) (assoc "TOTAL_EXCEDENTES" found))
        (progn
          (setq values counts)
          (foreach key tags
            (setq a (cdr (assoc key found)) d (entget a))
            (if (not (entmod (subst (cons 1 (itoa (car values))) (assoc 1 d) d)))
              (datra:fail "No se pudo actualizar atributo real del cajetin"))
            (setq values (cdr values)))
          (entupd e)
          (setq datra:*cajetin* "ACTUALIZADO_TOTAL_POSTES_TOTAL_CAJAS_TOTAL_EXCEDENTES"))
        (setq datra:*cajetin* "PENDIENTE_AJUSTE_PLANTILLA_ATRIBUTOS")))
    (setq datra:*cajetin* "PENDIENTE_AJUSTE_PLANTILLA_BLOQUE")))

(defun datra:finish (file points edges counts / stream selection actual i e d actualtypes p c x actualedges)
  (if (or (/= points datra:*points*) (/= edges datra:*edges*))
    (datra:fail "Conteos de insercion no coinciden"))
  (setq actual 0 p 0 c 0 x 0 actualedges 0
        selection (ssget "_X" '((0 . "INSERT") (410 . "Model") (-3 ("DATRA_CFE")))))
  (if selection
    (progn (setq i 0)
      (repeat (sslength selection)
        (setq e (ssname selection i) i (1+ i))
        (if (datra:owned e)
          (progn (setq actual (1+ actual) d (cdr (assoc 2 (entget e))))
            (cond ((= d "DATRA_POSTE_V1") (setq p (1+ p)))
                  ((= d "DATRA_CAJA_EMP_V1") (setq c (1+ c)))
                  ((= d "DATRA_EXCEDENTE_V1") (setq x (1+ x)))))))))
  (if (/= actual points) (datra:fail "Conteo real de bloques DATRA no coincide"))
  (if (not (equal counts (list p c x))) (datra:fail "Conteos reales por tipo no coinciden"))
  (setq selection (ssget "_X" '((0 . "LWPOLYLINE") (8 . "DATRA_RUTA") (-3 ("DATRA_CFE")))))
  (if selection
    (progn (setq i 0)
      (repeat (sslength selection)
        (if (datra:owned (ssname selection i)) (setq actualedges (1+ actualedges)))
        (setq i (1+ i)))))
  (if (/= edges actualedges) (datra:fail "Conteo real de aristas no coincide"))
  (datra:text "ESTADO" "DATRA_CONTROL" '(150.0 557.0 0.0) 3.0 datra:*mode* T)
  (datra:text "CONTEOS" "DATRA_CONTROL" '(150.0 552.0 0.0) 2.5
    (strcat "Componentes dibujados: " (itoa actual) " / Aristas: " (itoa edges)) T)
  (datra:cajetin (list p c x))
  (datra:text "PROTOTIPO" "DATRA_CONTROL" '(150.0 542.0 0.0) 2.0
    "SIMBOLOS ESQUEMATICOS - MATERIALES NO HOMOLOGADOS - REVISION HUMANA PENDIENTE" T)
  (if datra:*prototypes* (datra:details))
  (setq stream (open file "w"))
  (if (not stream) (datra:fail "No se pudo escribir evidencia nativa"))
  (write-line (strcat "modo=" datra:*mode*) stream)
  (write-line (strcat "bloques_insertados=" (itoa actual)) stream)
  (write-line (strcat "aristas=" (itoa edges)) stream)
  (write-line (strcat "POSTE=" (itoa p) ";CAJA_EMP=" (itoa c) ";EXCEDENTE=" (itoa x)) stream)
  (write-line (strcat "INSUNITS=" (itoa (getvar "INSUNITS"))) stream)
  (write-line (strcat "cajetin=" datra:*cajetin*) stream)
  (write-line "CRS/legibilidad/FINAL=REQUIERE_APROBACION_HUMANA" stream)
  (close stream)
  (setq datra:*ready* nil))

(defun datra:paper-line (id x1 y1 x2 y2)
  (datra:tag (datra:make (list '(0 . "LINE") '(8 . "DATRA_CONTROL") '(67 . 1)
    (cons 410 datra:*layout*) (list 10 x1 y1 0.0) (list 11 x2 y2 0.0))) id))

(defun datra:details (/ index y occupied id added sel i entity data)
  ; Solo esquemas ilustrativos en Paper, nunca instalaciones georreferenciadas.
  ; Si la base ya contiene geometria de detalle, preservarla sin superponer.
  (setq index 0)
  (foreach y '(499.0 389.0 279.0 169.0 59.0)
    (setq id (strcat "ESQUEMA-" (itoa index)))
    (setq occupied (ssget "_W" (list 18.0 (- y 40.0)) (list 132.0 (+ y 35.0))
      (list '(0 . "LINE,LWPOLYLINE,CIRCLE,INSERT,IMAGE") '(67 . 1) (cons 410 datra:*layout*))))
    (if (not occupied)
      (progn
        (setq added T)
        (datra:text id "DATRA_CONTROL" (list 23.0 (+ y 15.0) 0.0) 2.2 "PROTOTIPO NO HOMOLOGADO" T)
        (datra:text id "DATRA_CONTROL" (list 23.0 (- y 20.0) 0.0) 1.8 "SIN MATERIAL/CABLE ACREDITADO" T)
        (if (< index 4)
          (progn
            (datra:paper-line id 35.0 y 105.0 y)
            (datra:tag (datra:make (list '(0 . "CIRCLE") '(8 . "DATRA_CONTROL") '(67 . 1)
              (cons 410 datra:*layout*) (list 10 70.0 y 0.0) '(40 . 3.0))) id)
            (if (= index 2) (datra:paper-line id 70.0 y 95.0 (- y 12.0)))
            (if (= index 3)
              (progn (datra:paper-line id 65.0 (+ y 5.0) 75.0 (+ y 5.0))
                (datra:paper-line id 65.0 (- y 5.0) 75.0 (- y 5.0)))))
          (datra:text id "DATRA_CONTROL" (list 35.0 y 0.0) 2.5 "DETALLE POR DEFINIR" T))))
    (setq index (1+ index)))
  (if added
    (progn
      (setq sel (ssget "_X" (list '(0 . "TEXT") '(1 . "DETALLES APROBADOS") (cons 410 datra:*layout*))) i 0)
      (if sel
        (repeat (sslength sel)
          (setq entity (ssname sel i) i (1+ i) data (entget entity))
          (entmod (subst '(1 . "ESQUEMAS EN REVISION") (assoc 1 data) data)))))))

(defun datra:put (data code value)
  (if (assoc code data) (subst (cons code value) (assoc code data) data)
    (append data (list (cons code value)))))

(defun datra:viewport (xmin ymin xmax ymax / scale)
  (setq scale (max (/ (- xmax xmin) 410.0) (/ (- ymax ymin) 445.0) 0.01))
  (datra:camera (+ (/ (+ xmin xmax) 2.0) (* 50.0 scale)) (/ (+ ymin ymax) 2.0) scale))

(defun datra:camera (x y scale / sel i obj old area data vp previous-layer)
  ; AutoCAD prohíbe crear/modificar VIEWPORT mediante entmake/entmod.
  ; Crear por MVIEW y ajustar cámara con comandos globales; sin COM.
  (setvar "CTAB" datra:*layout*)
  (command "_.PSPACE")
  (setq old nil area 0.0 i 0 previous-layer (getvar "CLAYER"))
  (setq sel (ssget "_X" (list '(0 . "VIEWPORT") (cons 410 datra:*layout*))))
  (if sel
    (repeat (sslength sel)
      (setq obj (ssname sel i) i (1+ i) data (entget obj))
      (if (and (> (cdr (assoc 69 data)) 1) (> (cdr (assoc 40 data)) 100.0)
               (> (* (cdr (assoc 40 data)) (cdr (assoc 41 data))) area))
        (setq old obj area (* (cdr (assoc 40 data)) (cdr (assoc 41 data)))))))
  (setq data (if old (entget old)))
  (if (not (and datra:*symbol-scales* old
            (= (cdr (assoc 8 data)) "DATRA_VIEWPORTS")
            (equal (cdr (assoc 10 data)) '(410.0 302.5 0.0) 0.000001)
            (equal (cdr (assoc 40 data)) 530.0 0.000001)
            (equal (cdr (assoc 41 data)) 465.0 0.000001)
            (equal (cdr (assoc 12 data)) (list x y 0.0) 0.000001)
            (equal (cdr (assoc 45 data)) (* 465.0 scale) 0.000001)
            (= (logand 16384 (cdr (assoc 90 data))) 16384)))
   (progn
  (if old (entdel old))
  (setvar "CLAYER" "DATRA_VIEWPORTS")
  (command "_.UCS" "_World")
  (command "_.MVIEW" "_non" '(145.0 70.0) "_non" '(675.0 535.0))
  (setq vp (entlast))
  (setq datra:*created* (cons vp datra:*created*))
  (if (/= (cdr (assoc 0 (entget vp))) "VIEWPORT") (datra:fail "MVIEW no creo viewport"))
  (command "_.MSPACE")
  (setvar "CVPORT" (cdr (assoc 69 (entget vp))))
  (command "_.UCS" "_World")
  (command "_.PLAN" "_World")
  (command "_.ZOOM" "_C" "_non" (list x y) (* 465.0 scale))
  (command "_.PSPACE")
  (command "_.MVIEW" "_Lock" "_On" vp "")
  (setvar "CLAYER" previous-layer)
  (command "_.REGENALL"))))

(defun datra:inspect (expected file / stream lay data b selection)
  (datra:guard expected)
  (setq stream (open file "w"))
  (foreach variable '("DWGNAME" "DWGPREFIX" "INSUNITS" "UCSNAME" "WORLDUCS" "UCSORG" "UCSXDIR" "UCSYDIR" "CTAB" "TILEMODE" "PDFSHX")
    (write-line (strcat variable "=" (vl-princ-to-string (getvar variable))) stream))
  (foreach lay (datra:layouts)
    (setq data (entget (datra:layout-entity lay)))
    (write-line (strcat "LAYOUT=" lay ";MEDIA=" (cdr (assoc 4 data))
      ";DEVICE=" (cdr (assoc 2 data)) ";ROTATION=" (itoa (cdr (assoc 73 data)))) stream))
  (foreach table '("BLOCK" "LAYER" "STYLE")
    (setq b (tblnext table T))
    (while b (write-line (strcat table "=" (vl-princ-to-string b)) stream) (setq b (tblnext table))))
  (setq selection (ssget "_X" '((0 . "IMAGE,PDFUNDERLAY,DGNUNDERLAY,DWFUNDERLAY"))))
  (write-line (strcat "REFERENCIAS_RASTER_UNDERLAY=" (itoa (if selection (sslength selection) 0))) stream)
  (write-line "VERIFICAR_MANUALMENTE=logo,mapa,TENSION,SUSPENSION,DERIVACION,EMPALME,OTROS,fuentes,imagenes,escala,A1" stream)
  (close stream) (princ))

(defun c:DATRACONTROLES (/ p file stream)
  (if (not datra:*owner*) (datra:fail "Ejecute SCR01 sobre copia antes de capturar controles"))
  (setq file (strcat (getvar "DWGPREFIX") "controles_WCS_pendientes.txt") stream (open file "a"))
  (repeat 2
    (setq p (getpoint "\nSeleccione control fisico acreditable, distinto del anterior: "))
    (if (not p) (datra:fail "Captura cancelada"))
    (write-line (vl-princ-to-string (trans p 1 0)) stream))
  (close stream)
  (alert "Complete WGS84, evidencia, fecha, responsable y tolerancia en configuracion. Esta captura NO aprueba el CRS.")
  (princ))

(defun datra:evidence (expected file / f s i e d x a ad vertices id)
  ; Inspección read-only de geometría persistida, disponible también al reabrir.
  (datra:guard expected)
  (setq f (open file "w") i 0 s (ssget "_X" '((-3 ("DATRA_CFE")))))
  (write-line (strcat "ENGINE=" (getvar "ACADVER") ";MODE=" datra:*mode*) f)
  (if s (repeat (sslength s)
    (setq e (ssname s i) i (1+ i) d (entget e) x (assoc -3 (entget e '("DATRA_CFE"))))
    (if (datra:owned e)
     (progn
      (write-line (strcat (cdr (assoc 0 d)) "|" (cdr (nth 2 (cadr x))) "|"
        (vl-princ-to-string (vl-remove-if-not '(lambda (p) (member (car p) '(1 2 8 10 40 410))) d))) f)
      (if (and (= "LWPOLYLINE" (cdr (assoc 0 d))) (= "DATRA_RUTA" (cdr (assoc 8 d))))
        (progn
          (setq vertices (vl-remove-if-not '(lambda (p) (= (car p) 10)) d))
          (write-line (strcat "LENGTH|" (cdr (nth 2 (cadr x))) "|"
            (rtos (distance (cdr (car vertices)) (cdr (cadr vertices))) 2 12)) f)))))))
  (setq s (ssget "_X" (list '(0 . "INSERT") '(2 . "DATRA_CAJETIN_A1") (cons 410 datra:*layout*))) i 0)
  (if s (repeat (sslength s)
    (setq e (ssname s i) i (1+ i) a (entnext e))
    (while (and a (/= "SEQEND" (cdr (assoc 0 (setq ad (entget a))))))
      (write-line (strcat "ATTRIB|" (cdr (assoc 2 ad)) "|" (cdr (assoc 1 ad))) f)
      (setq a (entnext a)))))
  (write-line (strcat "WORLDUCS=" (itoa (getvar "WORLDUCS")) ";INSUNITS=" (itoa (getvar "INSUNITS")) ";PDFSHX=" (itoa (getvar "PDFSHX"))) f)
  (close f) (princ))
(princ)
