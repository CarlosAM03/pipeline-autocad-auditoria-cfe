;;; DATRA / CFE - solo lectura - diagnostico de detalles invisibles en PDF
;;; Comando CFECHEQUEODETALLES. No llama a SAVE/ENTMOD/VLA-PUT.
;;; Inspeccionar original 146468_PLANOTIJUANA y plantilla DATRA por separado.
(vl-load-com)

(defun cfed:asstr (v)
  (if (null v) "<nulo>" (vl-princ-to-string v))
)
(defun cfed:pair (f label val)
  (write-line (strcat label "\t" (cfed:asstr val)) f)
)
(defun cfed:layer (f name / rec flags)
  (setq rec (tblsearch "LAYER" name))
  (if rec
    (progn
      (setq flags (cdr (assoc 70 rec)))
      (cfed:pair f (strcat "LAYER " name " FLAGS") flags)
      (cfed:pair f (strcat "LAYER " name " COLOR") (cdr (assoc 62 rec)))
      (cfed:pair f (strcat "LAYER " name " PLOTFLAG") (cdr (assoc 290 rec)))
    )
    (cfed:pair f (strcat "LAYER " name) "NO EXISTE")
  )
)
(defun cfed:freepath (root stem / n path)
  (setq n 0)
  (setq path (strcat root stem "_detalles_layout.txt"))
  (while (findfile path)
    (setq n (1+ n))
    (setq path (strcat root stem "_detalles_layout_" (itoa n) ".txt"))
  )
  path
)
(defun c:CFECHEQUEODETALLES (/ root path f ss i d e l layname ss2 pair)
  (setq root "C:\\Users\\Carl0\\Desktop\\Datra\\CFE\\PipeLineDeAuditoria\\AuditoriaCFE\\Codex\\00_Diagnostico\\02_CAD_Origen\\")
  (cond
    ((not (vl-file-directory-p root))
     (princ (strcat "\nERROR: carpeta destino no existe: " root)))
    (T
      (setq path (cfed:freepath root (vl-filename-base (getvar "DWGNAME"))))
      (setq f (open path "w"))
      (if (null f)
        (princ "\nERROR: no se pudo abrir reporte")
        (progn
          (write-line "DATRA / CFE - DIAGNOSTICO DETALLES Y VIEWPORTS - SOLO LECTURA" f)
          (cfed:pair f "DWG" (getvar "DWGNAME"))
          (cfed:pair f "PREFIJO" (getvar "DWGPREFIX"))
          (cfed:pair f "LAYOUT_ACTIVO" (getvar "CTAB"))
          (cfed:pair f "UNIDADES_INSERCION" (getvar "INSUNITS"))
          (write-line "\n[CAPAS RELACIONADAS]" f)
          (foreach layname '("a-detalles" "DET_DIB" "a-pie" "a-text poste" "a-poste" "0")
            (cfed:layer f layname)
            (setq ss2 (ssget "_X" (list (cons 8 layname) (cons 410 "Model"))))
            (cfed:pair f (strcat "MODEL_ENTIDADES_CAPA " layname) (if ss2 (sslength ss2) 0))
          )
          (write-line "\n[VENTANAS EN PAPEL - CONTORNOS Y VISTAS]" f)
          (setq ss (ssget "_X" '((0 . "VIEWPORT"))))
          (if ss
            (progn
              (cfed:pair f "VIEWPORT_TOTAL" (sslength ss))
              (setq i 0)
              (while (< i (sslength ss))
                (setq e (ssname ss i) d (entget e))
                (write-line (strcat "\nVIEWPORT " (itoa (1+ i))) f)
                (foreach pair '((410 . "LAYOUT") (8 . "CAPA") (10 . "CENTRO_PAPEL")
                                (40 . "ALTO_PAPEL") (41 . "RELACION_ANCHO_ALTO")
                                (12 . "CENTRO_VISTA_MODELO") (45 . "ALTO_VISTA_MODELO")
                                (16 . "DIRECCION_VISTA") (68 . "ESTADO")
                                (69 . "IDENTIFICADOR_VIEWPORT") (90 . "FLAGS"))
                  (cfed:pair f (cdr pair) (cdr (assoc (car pair) d)))
                )
                (setq i (1+ i))
              )
            )
            (cfed:pair f "VIEWPORT_TOTAL" 0)
          )
          (write-line "\n[INTERPRETACION]" f)
          (write-line "Si a-detalles existe en Model pero no se ve en PDF, revisar VIEWPORT, VP Freeze y plot style." f)
          (write-line "Este inventario NO prueba la ubicacion ni la validez constructiva de cada detalle." f)
          (close f)
          (princ (strcat "\nCFECHEQUEODETALLES: " path))
        )
      )
    )
  )
  (princ)
)
(princ "\nCFE diagnostico cargado. Ejecute CFECHEQUEODETALLES.")
(princ)
